module onem2mall-impl {
    yang-version 1;
    namespace "urn:opendaylight:params:xml:ns:yang:onem2mall:impl";
    prefix "onem2mall-impl";

    import config { prefix config; revision-date 2013-04-05; }
    import opendaylight-md-sal-binding { prefix md-sal-binding; revision-date 2013-10-28;}

    description
        "Service definition for onem2mall project";

    revision "2014-12-10" {
        description
            "Initial revision";
    }

    identity onem2mall {
        base config:module-type;
        config:java-name-prefix Onem2mAll;
    }

    augment "/config:modules/config:module/config:configuration" {
        case onem2mall {
            when "/config:modules/config:module/config:type = 'onem2mall'";
            container broker {
                uses config:service-ref {
                    refine type {
                        mandatory true;
                        config:required-identity md-sal-binding:binding-broker-osgi-registry;
                    }
                }
            }
        }
    }
}
