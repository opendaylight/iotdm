/*
 * Copyright(c) 2016 Cisco Systems, Inc. and others.  All rights reserved.
 *
 * This program and the accompanying materials are made available under the
 * terms of the Eclipse Public License v1.0 which accompanies this distribution,
 * and is available at http://www.eclipse.org/legal/epl-v10.html
 *
 */
module onem2m-tsdr {
    yang-version 1;
    namespace "urn:opendaylight:params:xml:ns:yang:iotdm:onem2m:tsdr";
    prefix "onem2m-tsdr";

    import config { prefix config; revision-date 2013-04-05; }
    import opendaylight-md-sal-binding { prefix md-sal-binding; revision-date 2013-10-28;}
    import TSDR {prefix TSDR;revision-date "2015-02-19";}
    
    revision "2016-02-03" {
        description "Initial revision of the IoTDM onem2m tsdr integration";
    }

    identity onem2m-tsdr {
            base config:module-type;
            config:java-name-prefix Onem2mTsdr;
    }

    augment "/config:modules/config:module/config:configuration" {
                case onem2m-tsdr {
                    when "/config:modules/config:module/config:type = 'onem2m-tsdr'";
                    container rpc-registry {
                        uses config:service-ref {
                            refine type {
                                mandatory true;
                                config:required-identity md-sal-binding:binding-rpc-registry;
                            }
                        }
                    }
                }
            }


    rpc addTSDRMetricRecord {
         input {
             uses TSDR:TSDRMetric;
         }
    }

    rpc addTSDRLogRecord {
         input {
             uses TSDR:TSDRLog;
         }
    }
}
