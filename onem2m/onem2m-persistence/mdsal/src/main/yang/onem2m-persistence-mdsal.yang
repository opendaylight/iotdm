module onem2m-persistence-mdsal {
    yang-version 1;
    namespace "urn:opendaylight:params:xml:ns:yang:onem2m:persistence:mdsal";
    prefix "onem2m-persistence-mdsal";

    import config { prefix config; revision-date 2013-04-05; }
    import opendaylight-md-sal-binding { prefix md-sal-binding; revision-date 2013-10-28;}

    description
        "Service definition for onem2m project";

    revision "2014-12-10" {
        description
            "Initial revision";
    }

    identity onem2m-persistence-mdsal {
        base config:module-type;
        config:java-name-prefix Onem2mPersistenceMdsal;
    }

    augment "/config:modules/config:module/config:configuration" {
        case onem2m-persistence-mdsal {
            when "/config:modules/config:module/config:type = 'onem2m-persistence-mdsal'";
            container broker {
                uses config:service-ref {
                    refine type {
                        mandatory true;
                        config:required-identity md-sal-binding:binding-broker-osgi-registry;
                    }
                }
            }
        }
    }
}
