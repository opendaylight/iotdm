module onem2m-protocol-http {
    yang-version 1;
    namespace "urn:opendaylight:params:xml:ns:yang:onem2m:protocol:http";
    prefix "onem2m-protocol-http";

    import onem2m { prefix onem2m; revision-date 2015-01-05; }
    import iotdm-plugin-manager { prefix iotdm-plugin-manager; revision-date 2016-11-10; }
    import iotdm-comm-channel-http { prefix iotdm-comm-channel-coap; revision-date 2017-05-19; }
    import iotdm-comm-channels { prefix iotdm-comm-channels; revision-date 2017-05-19; }
    import ietf-inet-types {prefix inet; revision-date "2013-07-15";}

    description
        "Service definition for onem2m project";

    revision "2017-01-10" {
        description
            "Http module confiugration";
    }

    grouping http-protocol-server-config {
        leaf server-port {
            mandatory true;
            type inet:port-number;
        }

        leaf server-security-level {
            mandatory true;
            type onem2m:security-level;
        }

        leaf secure-connection {
            mandatory true;
            type boolean;
        }
    }

    grouping http-protocol-sender-config {
        leaf secure-connection {
            mandatory true;
            type boolean;
        }
    }

    grouping http-secure-connection-config {
        container key-store-config {
            description "Configuration of the Java KeyStore.";

            uses iotdm-comm-channels:java-key-store-config;
        }

        container trust-store-config {
            description "Configuration of the Java TrustStore (required by notifier plugin and router plugin).";

            leaf trust-store-file {
                description "Path to the Java TrustStore file.";
                mandatory true;
                type string;
            }

            leaf trust-store-password {
                description "Password to access the TrustStore file.";
                mandatory true;
                type string;
            }
        }
    }

    grouping http-protocol-provider-config {
        container server-config {
            uses http-protocol-server-config;
        }

        container https-config {
            presence "Required if the secure connection is set to true.";
            uses http-secure-connection-config;
        }

        container notifier-plugin-config {
            uses http-protocol-sender-config;
        }

        container router-plugin-config {
            uses http-protocol-sender-config;
        }
    }

    augment "/iotdm-plugin-manager:iotdm-plugin-manager-plugin-data
             /iotdm-plugin-manager:output
             /iotdm-plugin-manager:iotdm-plugin-manager-plugins-table
             /iotdm-plugin-manager:iotdm-plugin-manager-plugin-instances
             /iotdm-plugin-manager:plugin-configuration
             /iotdm-plugin-manager:plugin-specific-configuration" {
        case onem2m-http-https-config {
            uses http-protocol-provider-config;
        }
    }

    list onem2m-protocol-http-providers {
        key "http-provider-instance-name";
        leaf http-provider-instance-name {
            type string;
        }

        uses http-protocol-provider-config;
    }
}
