module onem2m-protocols-common {
    yang-version 1;
    namespace "urn:opendaylight:params:xml:ns:yang:onem2m:protocols:common";
    prefix "onem2m-protocols-common";

    description
        "Common definitions for onem2m protocols";

    revision "2014-12-10" {
        description
            "Initial revision";
    }
}
