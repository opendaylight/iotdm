module onem2m-protocol-mqtt {
    yang-version 1;
    namespace "urn:opendaylight:params:xml:ns:yang:onem2m:protocol:mqtt";
    prefix "onem2m-protocol-mqtt";

    import config { prefix config; revision-date 2013-04-05; }
    import opendaylight-md-sal-binding { prefix md-sal-binding; revision-date 2013-10-28;}
    import onem2m { prefix onem2m; revision-date 2015-01-05; }

    description
        "Service definition for onem2m project";

    revision "2014-12-10" {
        description
            "Initial revision";
    }

    identity onem2m-protocol-mqtt {
        base config:module-type;
        config:java-name-prefix Onem2mMqtt;
    }

    augment "/config:modules/config:module/config:configuration" {
        case onem2m-protocol-mqtt {
            when "/config:modules/config:module/config:type = 'onem2m-protocol-mqtt'";
            container broker {
                uses config:service-ref {
                    refine type {
                        mandatory true;
                        config:required-identity md-sal-binding:binding-broker-osgi-registry;
                    }
                }
            }

            container server-config {
                leaf server-security-level {
                    mandatory true;
                    type onem2m:security-level;
                }
                leaf mqtt-broker-ip {
                    type string;
                    description "tcp:<ipaddr> of the internal or external mqtt broker";
                }
                leaf mqtt-broker-port {
                    mandatory true;
                    type uint16;
                    description "port of the internal or external mqtt broker";
                }
                /*list cse-list {
                    leaf cse-id {
                        type string;
                        description "list of csi-id's for mqtt subscription";
                    }
                }*/
            }
        }
    }
}
