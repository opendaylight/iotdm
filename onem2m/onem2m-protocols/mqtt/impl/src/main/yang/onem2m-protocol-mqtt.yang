module onem2m-protocol-mqtt {
    yang-version 1;
    namespace "urn:opendaylight:params:xml:ns:yang:onem2m:protocol:mqtt";
    prefix "onem2m-protocol-mqtt";

    import onem2m { prefix onem2m; revision-date 2015-01-05; }
    import iotdm-plugin-manager { prefix iotdm-plugin-manager; revision-date 2016-11-10; }
    import ietf-inet-types {prefix inet; revision-date "2013-07-15";}

    description
        "Service definition for onem2m project";

    revision "2017-01-18" {
        description
            "MQTT module configuration";
    }

    grouping mqtt-client-config-definition {
        leaf security-level {
            mandatory true;
            type onem2m:security-level;
        }
        leaf mqtt-broker-ip {
            description "tcp:<ipaddr> of the internal or external mqtt broker";
            mandatory true;
            type inet:ipv4-address;
        }
        leaf mqtt-broker-port {
            description "Port of the internal or external mqtt broker";
            mandatory true;
            type inet:port-number;
        }
    }

    grouping mqtt-protocol-provider-config {
        container mqtt-client-config {
            presence "Mqtt client will not connect to broker if this configuration is not provided";
            uses mqtt-client-config-definition;
        }
    }

    augment "/iotdm-plugin-manager:iotdm-plugin-manager-plugin-data
             /iotdm-plugin-manager:output
             /iotdm-plugin-manager:iotdm-plugin-manager-plugins-table
             /iotdm-plugin-manager:iotdm-plugin-manager-plugin-instances
             /iotdm-plugin-manager:plugin-configuration
             /iotdm-plugin-manager:plugin-specific-configuration" {
        case onem2m-mqtt-config {
            uses mqtt-protocol-provider-config;
        }
    }

    list onem2m-protocol-mqtt-providers {
        key "mqtt-provider-instance-name";
        leaf mqtt-provider-instance-name {
            type string;
        }

        uses mqtt-protocol-provider-config;
    }
}
