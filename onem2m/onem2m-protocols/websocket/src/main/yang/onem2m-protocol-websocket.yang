module onem2m-protocol-websocket {
    yang-version 1;
    namespace "urn:opendaylight:params:xml:ns:yang:onem2m:protocol:websocket";
    prefix "onem2m-protocol-websocket";

    import onem2m { prefix onem2m; revision-date 2015-01-05; }
    import iotdm-plugin-manager { prefix iotdm-plugin-manager; revision-date 2016-11-10; }
    import ietf-inet-types {prefix inet; revision-date "2013-07-15";}

    description
        "Service definition for onem2m project";

    revision "2014-12-10" {
        description
            "Initial revision";
    }

    grouping websocket-protocol-server-config {
        leaf server-port {
            mandatory true;
            type inet:port-number;
        }

        leaf server-security-level {
            mandatory true;
            type onem2m:security-level;
        }
    }

    augment "/iotdm-plugin-manager:iotdm-plugin-manager-plugin-data
             /iotdm-plugin-manager:output
             /iotdm-plugin-manager:iotdm-plugin-manager-plugins-table
             /iotdm-plugin-manager:iotdm-plugin-manager-plugin-instances
             /iotdm-plugin-manager:plugin-configuration
             /iotdm-plugin-manager:plugin-specific-configuration" {
        case onem2m-websocket-config {
            uses websocket-protocol-server-config;
        }
    }

    list onem2m-protocol-websocket-providers {
        key "websocket-provider-instance-name";
        leaf websocket-provider-instance-name {
            type string;
        }

        uses websocket-protocol-server-config;
    }
}
