module onem2m-protocol-coap {
    yang-version 1;
    namespace "urn:opendaylight:params:xml:ns:yang:onem2m:protocol:coap";
    prefix "onem2m-protocol-coap";

    import config { prefix config; revision-date 2013-04-05; }
    import opendaylight-md-sal-binding { prefix md-sal-binding; revision-date 2013-10-28;}
    import onem2m { prefix onem2m; revision-date 2015-01-05; }
    import onem2m-plugin-manager { prefix onem2m-plugin-manager; revision-date 2016-11-10; }

    description
        "Service definition for onem2m project";

    revision "2014-12-10" {
        description
            "Initial revision";
    }

    identity onem2m-protocol-coap {
        base config:module-type;
        config:java-name-prefix Onem2mCoap;
    }

    grouping coap-channel-common-config {
        leaf secure-connection {
            mandatory true;
            type boolean;
        }
        leaf use-preshared-keys {
            type boolean;
        }
    }

    grouping coap-security-config {
        container dtls-certificates-config {
            container key-store-config {
                uses onem2m-plugin-manager:coaps-keystore-config;
            }
            container trust-store-config {
                leaf trust-store-file {
                    mandatory true;
                    type string;
                }
                leaf trust-store-password {
                    mandatory true;
                    type string;
                }
                list trusted-certificates {
                    leaf certificate-name {
                        type string;
                    }
                }
            }
        }

        container dtls-psk-local-cse-base {
            uses onem2m-plugin-manager:coaps-psk-config;
        }

        container dtls-psk-remote-cse {
            uses onem2m-plugin-manager:coaps-psk-config;
        }
    }

    augment "/config:modules/config:module/config:configuration" {
        case onem2m-protocol-coap {
            when "/config:modules/config:module/config:type = 'onem2m-protocol-coap'";
            container broker {
                uses config:service-ref {
                    refine type {
                        mandatory true;
                        config:required-identity md-sal-binding:binding-broker-osgi-registry;
                    }
                }
            }
            container server-config {
                leaf server-port {
                    mandatory true;
                    type uint16;
                }
                leaf server-security-level {
                    mandatory true;
                    type onem2m:security-level;
                }

                uses coap-channel-common-config;
            }

            container notifier-plugin-config {
                uses coap-channel-common-config;
            }

            container router-plugin-config {
                uses coap-channel-common-config;
            }

            container coaps-config {
                uses coap-security-config;
            }
        }
    }
}
