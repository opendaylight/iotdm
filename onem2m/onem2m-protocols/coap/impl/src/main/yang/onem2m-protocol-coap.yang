module onem2m-protocol-coap {
    yang-version 1;
    namespace "urn:opendaylight:params:xml:ns:yang:onem2m:protocol:coap";
    prefix "onem2m-protocol-coap";

    import onem2m { prefix onem2m; revision-date 2015-01-05; }
    import iotdm-plugin-manager { prefix iotdm-plugin-manager; revision-date 2016-11-10; }
    import iotdm-comm-channel-coap { prefix iotdm-comm-channel-coap; revision-date 2017-05-19; }
    import ietf-inet-types {prefix inet; revision-date "2013-07-15";}

    description
        "Service definition for onem2m project";

    revision "2017-01-16" {
        description
            "Coap Module Configuration";
    }

    grouping coap-channel-common-config {
        leaf secure-connection {
            mandatory true;
            type boolean;
        }
        leaf use-preshared-keys {
            type boolean;
        }
    }

    grouping coap-security-config {
        container dtls-certificates-config {
            container key-store-config {
                uses iotdm-comm-channel-coap:coaps-keystore-config;
            }
            container trust-store-config {
                leaf trust-store-file {
                    mandatory true;
                    type string;
                }
                leaf trust-store-password {
                    mandatory true;
                    type string;
                }
                list trusted-certificates {
                    leaf certificate-name {
                        type string;
                    }
                }
            }
        }

        container dtls-psk-local-cse-base {
            uses iotdm-comm-channel-coap:coaps-psk-config;
        }

        container dtls-psk-remote-cse {
            uses iotdm-comm-channel-coap:coaps-psk-config;
        }
    }

    grouping coap-protocol-provider-config {

        container server-config {
            leaf server-port {
                mandatory true;
                type inet:port-number;
            }
            leaf server-security-level {
                mandatory true;
                type onem2m:security-level;
            }

            uses coap-channel-common-config;
        }

        container coaps-config {
            presence "Required if the secure-connection is set true.";
            uses coap-security-config;
        }

        container notifier-plugin-config {
            uses coap-channel-common-config;
        }

        container router-plugin-config {
            uses coap-channel-common-config;
        }
    }

    augment "/iotdm-plugin-manager:iotdm-plugin-manager-plugin-data
             /iotdm-plugin-manager:output
             /iotdm-plugin-manager:iotdm-plugin-manager-plugins-table
             /iotdm-plugin-manager:iotdm-plugin-manager-plugin-instances
             /iotdm-plugin-manager:plugin-configuration
             /iotdm-plugin-manager:plugin-specific-configuration" {
        case onem2m-coap-coaps-config {
            uses coap-protocol-provider-config;
        }
    }

    list onem2m-protocol-coap-providers {
        key "coap-provider-instance-name";
        leaf coap-provider-instance-name {
            type string;
        }
        uses coap-protocol-provider-config;
    }
}
