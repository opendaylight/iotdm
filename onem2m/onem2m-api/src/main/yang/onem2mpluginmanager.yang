module onem2m-plugin-manager {
    yang-version 1;
    namespace "urn:opendaylight:params:xml:ns:yang:iotdm:onem2mpluginmanager";
    prefix onem2m-plugin-manager;

    import onem2m-simple-config { prefix onem2m-simple-config; revision-date 2016-11-22; }

    description "Onem2m PluginManager data models and RPCs.";

    revision "2016-11-10" {
        description "Initial revision of onem2m-plugin-manager yang module.";
    }


    /*
     * Communication channel configurations definitions
     */
    grouping java-key-store-config {
        leaf key-store-file {
            description "Path to the Java KeyStore file.";
            mandatory true;
            type string;
        }

        leaf key-store-password {
            description "Password to access the KeyStore file.";
            mandatory true;
            type string;
        }

        leaf key-manager-password {
            description "Password for key manager (needed if different from the key-store-password).";
            mandatory false;
            type string;
        }
    }

    grouping coaps-keystore-config {
        uses java-key-store-config;

        leaf key-alias {
            mandatory true;
            type string;
        }
    }

    grouping coaps-psk-config {
        list cse-psk {
            key cse-id;
            leaf cse-id {
                type string;
            }
            leaf psk {
                type string;
            }
        }
    }

    grouping coaps-channel-config-definition {
        choice coaps-channel-config-options {
            case coaps-keystore-config-options {
                uses coaps-keystore-config;
            }
            case coaps-psk-config-options {
                uses coaps-psk-config;
            }
        }
    }


    /*
     * Onem2m PluginManager data definitions and RPCs
     */
     grouping iotdm-plugin-data-definition {
         container iotdm-common-plugin-data {
            description "Plugin data common for all plugins.";

            leaf plugin-name {
                description "Name of the plugin.";
                mandatory true;
                type string;
            }

            leaf plugin-instance-name {
                description "Unique plugin instance name.";
                mandatory true;
                type string;
            }

            leaf plugin-class {
                description "Class of the plugin.";
                mandatory true;
                type string;
            }

            leaf plugin-loader {
                description
                    "Name of the PluginLoader instance used to load the plugin. " +
                    "This item is not set if the plugin is loaded as ODL module without PluginLoader.";
                type string;
            }
         }
     }

    grouping iotdm-plugin-filters {
        leaf plugin-name {
            description "Name of the plugin implementation.";
            type string;
        }

        leaf plugin-instance-name {
            description "Unique name of plugin instance.";
            type string;
        }

        leaf plugin-loader-name {
            description "Filter plugins loaded by specific plugin loader.";
            type string;
        }
    }

    /*
     * Get table of plugins registered in plugin manager
     */
    grouping iotdm-plugin-registration-data-definition {
        container registration-data {
            description "Data identifying unique registration of instance of IotdmPlugin.";
            leaf protocol {
                description "Registered protocol.";
                mandatory true;
                type string;
            }

            leaf address {
                description
                    "Meaning depends on communication channel type used. " +
                    "Value is local interface address in case of server channel or " +
                    "the value is remote address of destination in case of client channel.";
                type string;
            }

            leaf port {
                description "Meaning depends on communication channel type used. " +
                            "Value is local port registered in case of server channel or " +
                            "the value is remote port of destination in case of client channel.";
                mandatory true;
                type uint16;
            }

            leaf transport-protocol {
                description "Transport protocol type used.";
                mandatory true;
                type string;
            }

            leaf local-url {
                description "Local URL in Onem2m form for which the plugin is registered.";
                type string;
            }

            leaf registration-mode {
                description "Registration mode used.";
                mandatory true;
                type string;
            }
        }
    }

    grouping iotdm-plugin-instance-registration-data-definition {
        uses iotdm-plugin-data-definition;

        list iotdm-plugin-registrations {
            description "List of registration data of IotdmPlugin instances.";
            uses iotdm-plugin-registration-data-definition;
        }
    }

    rpc onem2m-plugin-manager-iotdm-plugin-registrations {
        description
          "Returns table of registered plugin instances implementing IotdmPlugin.";

        input {
            uses iotdm-plugin-filters;
        }

        output {
            list registered-iotdm-plugins-table {
                description "Table of all plugins implementing IotdmPlugin interface.";

                key "plugin-name";
                leaf plugin-name {
                    description "Name of the plugin implementation.";
                    mandatory true;
                    type string;
                }

                list registered-iotdm-plugin-instances {
                    key "plugin-instance-name";
                    leaf plugin-instance-name {
                        description "Unique plugin instance name.";
                        mandatory true;
                        type string;
                    }

                    uses iotdm-plugin-instance-registration-data-definition;
                }
            }
        }
    }


    /*
     * Get communication channels data
     */
    grouping onem2m-communication-channel-data-definition {
        container channel-data {
            description "Data describing CommunicationChannel instance.";

            leaf channel-type {
                description "Type of communication channel used.";
                mandatory true;
                type string;
            }

            leaf protocol {
                description "Registered protocol.";
                mandatory true;
                type string;
            }

            leaf address {
                description "IP address of local interface for servers or remote interface for clients.";
                type string;
            }

            leaf port {
                description "UDP or TCP port on local interface for servers or remote interface for clients.";
                type uint16;
            }

            leaf transport-protocol {
                description "Transport protocol type used.";
                mandatory true;
                type string;
            }

            leaf channel-state {
                description "Current state of the communication channel.";
                type string;
            }

            container channel-configuration {
                description "Configuration of the CommunicationChannel.";

                leaf is-default {
                    description "Is set to True if the default configuration is used. " +
                                "False value is used if the registered plugin(s) used own configuration.";
                    mandatory true;
                    type boolean;
                }

                choice channel-specific-configuration {
                    description "Current configuration of the channel.";
                    case https-channel-config {
                        uses java-key-store-config;
                    }
                    case coaps-channel-config {
                        uses coaps-channel-config-definition;
                    }
                }
            }
        }

        list iotdm-plugins {
            description "List of IotdmPlugins registered to use this CommunicationChannel instance.";
            key "iotdm-plugin-name";

            leaf iotdm-plugin-name {
                description "Name of the plugin implementation.";
                type string;
                mandatory true;
            }

            list iotdm-plugin-instances {
                description "List of instances of the plugin implementation.";
                key "iotdm-plugin-instance-id";

                leaf iotdm-plugin-instance-id {
                    description "Unique instance ID.";
                    type string;
                    mandatory true;
                }
            }
        }
    }

    rpc onem2m-plugin-manager-communication-channels {
        description "Returns table of CommunicationChannel instances.";

        input {
            leaf protocol-name {
                description "Optional attribute used to filter CommunicationChannel instances " +
                            "implementing specific protocol.";
                type string;
            }

            leaf plugin-name {
                description "Name of the plugin implementation.";
                type string;
            }

            leaf plugin-instance-name {
                description "Unique name of plugin instance.";
                type string;
            }
        }

        output {
            list onem2m-communication-channel-protocols {
                description "List of CommunicationChannel instances per protocol, address and port.";
                key "communication-channel-protocol";

                leaf communication-channel-protocol {
                    type string;
                    mandatory true;
                }

                list onem2m-communication-channel-addresses {
                    description "List of CommunicationChannel instances per address and port.";
                    key "communication-channel-address";

                    leaf communication-channel-address {
                        type string;
                        mandatory true;
                    }

                    list onem2m-communication-channel-ports {
                        description "List of CommunicationChannel instances per port number.";
                        key "onem2m-communication-channel-port";

                        leaf onem2m-communication-channel-port {
                            type uint16;
                            mandatory true;
                        }

                        uses onem2m-communication-channel-data-definition;
                    }
                }
            }
        }
    }


    /*
     * Get registrations of DB API client plugins
     */
     grouping onem2m-db-api-client-registration-definition {
        container db-api-client-plugin-data {
            uses iotdm-plugin-data-definition;

            leaf db-api-client-state {
                description "State of the DB API Client plugin.";
                type string;
                mandatory true;
            }
        }
     }

     rpc onem2m-plugin-manager-db-api-client-registrations {
        description "Returns table of registered plugin instances implementing DB API Client interface.";

        input {
            uses iotdm-plugin-filters;
        }

        output {
            list registered-db-api-client-plugins-table {
                description "Table of plugins implementing DB API client interface.";
                key "plugin-name";

                leaf plugin-name {
                    description "Name of the plugin implementation.";
                    mandatory true;
                    type string;
                }

                list registered-db-api-client-plugin-instances {
                    key "plugin-instance-name";
                    leaf plugin-instance-name {
                        description "Unique plugin instance name.";
                        mandatory true;
                        type string;
                    }

                    uses onem2m-db-api-client-registration-definition;
                }
            }
        }
     }


    /*
     * Get registrations of SimpleConfig client plugins
     */
     rpc onem2m-plugin-manager-simple-config-client-registrations {
        description "Returns table of registered plugin instances implementing SimpleConfig client interface.";

        input {
            uses iotdm-plugin-filters;
        }

        output {
            list registered-simple-config-client-plugins-table {
                key "plugin-name";
                leaf plugin-name {
                    description "Name of the plugin implementation.";
                    mandatory true;
                    type string;
                }

                list registered-simple-config-client-plugin-instances {
                    key "plugin-instance-name";
                    leaf plugin-instance-name {
                        description "Unique plugin instance name.";
                        mandatory true;
                        type string;
                    }

                    uses iotdm-plugin-data-definition;

                    uses onem2m-simple-config:plugin-simple-config-definition;
                }
            }
        }
     }


     /*
      * Get complete plugin data
      */
     rpc onem2m-plugin-manager-plugin-data {
        description "Returns all PluginManager data about plugin instances matching input filters.";

        input {
            uses iotdm-plugin-filters;
        }

        output {
            list onem2m-plugin-manager-plugins-table {
                key "plugin-name";
                leaf plugin-name {
                    description "Name of the plugin implementation.";
                    mandatory true;
                    type string;
                }

                list  onem2m-plugin-manager-plugin-instances {
                    key "plugin-instance-name";
                    leaf plugin-instance-name {
                        description "Unique plugin instance name.";
                        mandatory true;
                        type string;
                    }

                    /* Implemented Iotdm Plugin interfaces */
                    list implemented-interfaces {
                        description "List of implemented Iotdm interfaces.";
                        key "iotdm-interface";

                        leaf iotdm-interface {
                            type string;
                        }
                    }

                    /* IotdmPlugin data */
                    uses iotdm-plugin-instance-registration-data-definition;

                    /* DB API data */
                    container db-api-client-data {
                        description "Data related to plugins implementing DB API client interface.";
                        leaf db-api-client-state {
                            type string;
                        }
                    }

                    /* Plugin configuration */
                    container plugin-configuration {
                        choice plugin-specific-configuration {
                            description "Configuration of the plugin instance.";
                            case simple-config {
                                uses onem2m-simple-config:plugin-simple-config-definition;
                            }
                        }
                    }

                    /* TODO errors */
                }
            }
        }
     }
}
