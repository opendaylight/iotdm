module onem2m-comm-channel-coap {
    yang-version 1;
    namespace "urn:opendaylight:params:xml:ns:yang:iotdm:onem2m:commchannels:coap";
    prefix "onem2m-comm-channel-coap";

    import iotdm-comm-channel-coap { prefix iotdm-comm-channel-coap; revision-date 2017-05-19; }
    import iotdm-plugin-manager { prefix iotdm-polugin-manager; revision-date 2016-11-10; }

    description
        "Defintions of model of OneM2M CoAP(S) communication channel ";

    revision "2017-05-19" {
        description
            "Initial revision of onem2m-comm-channel-coap model";
    }

    augment "iotdm-plugin-manager:iotdm-plugin-manager-communication-channels/
             iotdm-plugin-manager:output/
             iotdm-plugin-manager:iotdm-communication-channel-protocols/
             iotdm-plugin-manager:iotdm-communication-channel-addresses/
             iotdm-plugin-manager:iotdm-communication-channel-ports/
             iotdm-plugin-manager:channel-data/
             iotdm-plugin-manager:channel-configuration/
             iotdm-plugin-manager:channel-specific-configuration" {

        case onem2m-coaps-channel-config {
            uses iotdm-comm-channel-coap:coaps-channel-config-definition;
        }
    }
}
