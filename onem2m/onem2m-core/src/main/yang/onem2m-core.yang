module onem2m-core {
    yang-version 1;
    namespace "urn:opendaylight:params:xml:ns:yang:onem2m:core";
    prefix "onem2m-core";

    import opendaylight-md-sal-binding { prefix md-sal-binding; revision-date 2013-10-28;}
    import onem2m { prefix onem2m; revision-date 2015-01-05; }
    import iotdm-comm-channel-coap { prefix iotdm-comm-channel-coap; revision-date 2017-05-19; }
    import iotdm-comm-channel-http { prefix iotdm-comm-channel-http; revision-date 2017-05-19; }
    import iotdm-comm-channels { prefix iotdm-comm-channels; revision-date 2017-05-19; }

    description
        "Service definition for onem2m project";

    revision "2014-12-10" {
        description "Initial revision";
    }

    grouping onem2m-core-security-config {
        container security-config {
            leaf core-security-level {
                mandatory true;
                type onem2m:security-level;
            }
        }
    }

    grouping onem2m-core-https-config {
        container default-https-config {
            description "Default configuration of Java KeyStore file which is used for HTTPS connections by default.";
            uses iotdm-comm-channels:java-key-store-config;
        }
    }

    grouping onem2m-core-coaps-config {
        container default-coaps-config {
            description "Default configuration of Java KeyStore file and PresharedKeys used for CoAPS communication by default.";
            uses iotdm-comm-channel-coap:coaps-keystore-config;
            uses iotdm-comm-channel-coap:coaps-psk-config;
        }
    }

    container onem2m-core-config {
        uses onem2m-core-security-config;
        uses onem2m-core-https-config;
        uses onem2m-core-coaps-config;
    }
}
