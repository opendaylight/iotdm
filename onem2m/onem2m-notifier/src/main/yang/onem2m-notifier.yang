module onem2m-notifier {
    yang-version 1;
    namespace "urn:opendaylight:params:xml:ns:yang:onem2m:notifier";
    prefix "onem2m-notifier";

    import config { prefix config; revision-date 2013-04-05; }
    import opendaylight-md-sal-binding { prefix md-sal-binding; revision-date 2013-10-28;}

    description
        "Service definition for onem2m project";

    revision "2014-12-10" {
        description
            "Initial revision";
    }

    identity onem2m-notifier {
        base config:module-type;
        config:java-name-prefix Onem2mNotifier;
    }

    augment "/config:modules/config:module/config:configuration" {
        case onem2m-notifier {
            when "/config:modules/config:module/config:type = 'onem2m-notifier'";
            container notification-service {
                uses config:service-ref {
                    refine type {
                        mandatory true;
                        config:required-identity md-sal-binding:binding-notification-service;
                    }
                }
            }
        }
    }
}
