/*
 * Copyright(c) 2016 Cisco Systems, Inc. and others.  All rights reserved.
 *
 * This program and the accompanying materials are made available under the
 * terms of the Eclipse Public License v1.0 which accompanies this distribution,
 * and is available at http://www.eclipse.org/legal/epl-v10.html
 *
 */

module onem2moic {
    yang-version 1;
    namespace "urn:opendaylight:params:xml:ns:yang:onem2moic";
    prefix "onem2moic";

    revision "2016-09-29" {
        description "Initial revision of onem2moic model";
    }

    container onem2m-oic-config {
        /*
         * There exist three variants of how interworking through an Inter-working Proxy Application Entity over
         * Mca can be supported:
         * 1. Interworking with full mapping of the semantic of the non-oneM2M data model to Mca
         * 2. Interworking using containers for transparent transport of encoded non-oneM2M data and commands via Mca
         * 3. Interworking using a retargeting mechanism
         * Please check TS-0001-V2.9.1 OneM2M Functional Architecture Appendix F.
         * For now, OIC plugin only supports option 2.
         */
        leaf ipe-mode {
            mandatory true;
            type enumeration {
                enum "FULL_MAPPING" {
                    value 1;
                    description "Interworking with full mapping of the semantic of the non-oneM2M data model to Mca";
                }
                enum "TRANSPARENT_TRANSPORT" {
                    value 2;
                    description "Interworking using containers for transparent transport of encoded non-oneM2M data and commands via Mca";
                }
                enum "RETARGET" {
                    value 3;
                    description "Interworking using a retargeting mechanism";
                }
            }
            default 2;
            description "What kind of IPE mode";
        }

        /*
         * OIC Plugin (OIC IPE) participates in OIC protocol in the role of OIC client. OIC IPE discovers the
         * OIC servers (Endpoints/Applications) by registering to "All Coap Nodes" multicast group and
         * requesting for OIC devices and resources. The details that the OIC Client gets become stale or invalid
         * once the time to live expires. OIC client has to periodically poll for keeping the OIC devices/resources
         * up to date.
         */
        leaf poll-period {
            mandatory true;
            type uint16;
            description "Number of seconds upon which OIC client updates OIC Devices";
        }

        /*
         * CSE name under which OIC devices will be mapped in Onem2m resource tree
         */
        leaf cse-name {
            mandatory true;
            type string;
            default "InCSE1";
            description "CSE name under which OIC devices will be mapped in Onem2m resource tree";
        }

        /*
         * IP address of the local interface which is used for OIC discovery
         */
         leaf local-ip-addr {
            type string;
            default "";
            description "IP address of the local interface using which OIC performs discovery";
         }
    }
}
