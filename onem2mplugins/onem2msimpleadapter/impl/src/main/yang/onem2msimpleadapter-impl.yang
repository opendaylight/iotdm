module onem2msimpleadapter-impl {
    yang-version 1;
    namespace "urn:opendaylight:params:xml:ns:yang:onem2msimpleadapter:impl";
    prefix "onem2msimpleadapter-impl";

    import config { prefix config; revision-date 2013-04-05; }
    import opendaylight-md-sal-binding { prefix md-sal-binding; revision-date 2013-10-28;}

    description
        "Service definition for onem2msimpleadapter project";

    revision "2014-12-10" {
        description
            "Initial revision";
    }

    identity onem2msimpleadapter {
        base config:module-type;
        config:java-name-prefix Onem2mSimpleAdapter;
    }

    augment "/config:modules/config:module/config:configuration" {
        case onem2msimpleadapter {
            when "/config:modules/config:module/config:type = 'onem2msimpleadapter'";
            container broker {
                uses config:service-ref {
                    refine type {
                        mandatory true;
                        config:required-identity md-sal-binding:binding-broker-osgi-registry;
                    }
                }
            }
        }
    }
}
