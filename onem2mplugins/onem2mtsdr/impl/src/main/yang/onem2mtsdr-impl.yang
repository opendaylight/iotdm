module onem2mtsdr-impl {
    yang-version 1;
    namespace "urn:opendaylight:params:xml:ns:yang:onem2mtsdr:impl";
    prefix "onem2mtsdr-impl";

    import config { prefix config; revision-date 2013-04-05; }
    import opendaylight-md-sal-binding { prefix md-sal-binding; revision-date 2013-10-28;}

    description
        "Service definition for onem2mtsdr project";

    revision "2014-12-10" {
        description
            "Initial revision";
    }

    identity onem2mtsdr {
        base config:module-type;
        config:java-name-prefix Onem2mTsdr;
    }

    augment "/config:modules/config:module/config:configuration" {
        case onem2mtsdr {
            when "/config:modules/config:module/config:type = 'onem2mtsdr'";
            container broker {
                uses config:service-ref {
                    refine type {
                        mandatory true;
                        config:required-identity md-sal-binding:binding-broker-osgi-registry;
                    }
                }
            }
        }
    }
}
