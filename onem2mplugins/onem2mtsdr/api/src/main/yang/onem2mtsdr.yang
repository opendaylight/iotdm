/*
 * Copyright(c) 2016 Cisco Systems, Inc. and others.  All rights reserved.
 *
 * This program and the accompanying materials are made available under the
 * terms of the Eclipse Public License v1.0 which accompanies this distribution,
 * and is available at http://www.eclipse.org/legal/epl-v10.html
 *
 */

 module onem2mtsdr {
    yang-version 1;
    namespace "urn:opendaylight:params:xml:ns:yang:onem2mtsdr";
    prefix "onem2mtsdr";

    revision "2016-02-10" {
        description "Initial revision of onem2mtsdr model";
    }

    grouping tsdr-parms-desc {

        leaf poll-period {
            mandatory true;
            type uint32;
            description "Number of seconds between sending data to TSDR in POLL mode, N/A for ASYNC";
        }

        /*
        ** The content-type is used to filter the type of data that gets sent to the TSDR.  The oneM2M resource tree
        ** models many different types of resources and it is likely that only "real" IOT data is sent to the tsdr.
        ** Example: an IOT sensor puts a latest value for a temperature reading in to the content instance resource
        ** of a container.  The url might be something like /cseName/tempSensorDeviceApp/thermometer10/latest/con/98.6
        ** The TSDR would like a time series of temperature readings.  The type would be LATEST-CI-CON-METRIC.  However,
        ** if the con field contains a JSON rep of the reading like {"temp":98.6}, then the type might be
        ** LATEST-CI-CON-LOG as the whole JSON rep is logged to tsdr.  The TSDR system can handle LOG and METRIC where
        ** log is basically a blob of data, and METRIC is a (decimal) value.  The METRIC is typically used to handle
        ** pkt counters, byte counters, like for networking devices.  It can also be used for IOT sensor readings that
        ** are interpreted as numbers.
        **
        ** My hope is that these enums are enough to handle ALL cases ... if not, maybe we add some more, or you
        ** need to write some custom handlers for your data before you send it to TSDR.
        */
        leaf content-type {
            mandatory true;
            type enumeration {
                enum "LATEST-CI" {
                    value 1;
                    description "Send the content instance resource json record using tsdr log api";
                }
                enum "LATEST-CI-CON-TSDR-LOG" {
                    value 2;
                    description "Send only the content instance con field using tsdr log api";
                }
                enum "LATEST-CI-CON-TSDR-METRIC" {
                    value 3;
                    description "Send only the content instance con field using tsdr metric api";
                }
                enum "ANY-RESOURCE" {
                    value 4;
                    description "Send any onem2m resource json record using tsdr log api";
                }
            }
            description "What kind of onem2m content should be sent";
        }

        leaf parse-json-content-into-tsdr-attrs-enabled {
            mandatory true;
            type boolean;
            description "If TRUE, parse json content and put key/value into tsdr attributes";
        }

        /*
        ** The mode dictates how data makes its way into the tsdr database.
        ** 1) POLL: the plugin will POLL the onem2m tree based on the setting of contentType based on the poll period.
        **    When the timer goes off, all content under the onem2m-target will be polled and the data is
        **    sent to the tsdr.  The content is subject to the contentType described above.
        ** 2) ASYNC: asynchronous updates occur to the onem2m datastore.  As these updates occur, these updates are
        **    sent to the tsdr.
        */
        leaf tsdr-mode {
            mandatory true;
            type enumeration {
                enum "POLL" {
                    value 1;
                    description "Find all appropriate data every polling period and send it to tsdr";
                }
                enum "ASYNC" {
                    value 2;
                    description "As data arrives in the data store, buffer it up, and send it every n batch seconds";
                }
            }
            description "What kind of onem2m content should be sent";
        }
    }

    container onem2m-tsdr-config {

        leaf tsdr-node-id {
            type string;
            description "The ID of the network element";
        }

        /*
        ** To be nice to the TSDR system, data is batched and sent periodically.  As ASYNC data is processed, it it
        ** queued/batched by the onem2m-tsdr module until the time expires.  For POLL data, it is possible that the poll
        ** cycle collects alot of data, it too is queued/batched and sent when the batch timer expires. Note that all
        ** data to be collected is timestamped when it is POLL-ed or when AYNC changes happen, NOT when it is sent as a
        ** batch to the TSDR module.
        */
        leaf batch-period-seconds {
            type uint32;
            default 15;
            description "Regardless of tsdr-mode, tsdr data is batched and sent periodically using this timer";
        }

        /*
        ** The oneM2M resource tree can be large, it might be desirebale to be flexible as to which nodes in the tree
        ** will be sent to the TSDR and how.  Some nodes might wish to be sent ASYNC when the tree is updated.  Some
        ** nodes might which to be POLLed periodically, and ONLY the current value of the latest content instance is
        ** sent.  It really depends if the user wishes not to miss any updates.
        */
        list onem2m-target-desc {
            key onem2m-target-uri;
            leaf onem2m-target-uri {
                type string;
            }
            uses tsdr-parms-desc;
        }
    }
}
