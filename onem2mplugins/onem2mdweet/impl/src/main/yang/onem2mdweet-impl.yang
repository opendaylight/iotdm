module onem2mdweet-impl {
    yang-version 1;
    namespace "urn:opendaylight:params:xml:ns:yang:onem2mdweet:impl";
    prefix "onem2mdweet-impl";

    import config { prefix config; revision-date 2013-04-05; }
    import opendaylight-md-sal-binding { prefix md-sal-binding; revision-date 2013-10-28;}

    description
        "Service definition for onem2mdweet project";

    revision "2014-12-10" {
        description
            "Initial revision";
    }

    identity onem2mdweet {
        base config:module-type;
        config:java-name-prefix Onem2mDweet;
    }

    augment "/config:modules/config:module/config:configuration" {
        case onem2mdweet {
            when "/config:modules/config:module/config:type = 'onem2mdweet'";
            container broker {
                uses config:service-ref {
                    refine type {
                        mandatory true;
                        config:required-identity md-sal-binding:binding-broker-osgi-registry;
                    }
                }
            }
        }
    }
}
