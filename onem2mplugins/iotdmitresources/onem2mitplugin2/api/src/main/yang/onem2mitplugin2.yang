module onem2mitplugin2 {
    yang-version 1;
    namespace "urn:opendaylight:params:xml:ns:yang:onem2mitplugin2";
    prefix "onem2mitplugin2";

    revision "2015-01-05" {
        description "Initial revision of onem2mitplugin2 model";
    }
}
