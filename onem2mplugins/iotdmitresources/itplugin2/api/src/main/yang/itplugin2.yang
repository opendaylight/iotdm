module itplugin2 {
    yang-version 1;
    namespace "urn:opendaylight:params:xml:ns:yang:iotdm:testing:itplugin2";
    prefix "itplugin2";

    revision "2017-02-06" {
        description "Initial revision of itplugin2 model";
    }
}
