module onem2mbenchmark {
    yang-version 1;
    namespace "urn:opendaylight:params:xml:ns:yang:onem2mbenchmark";
    prefix "onem2mbenchmark";

    revision "2015-01-05" {
        description "Initial revision of onem2mbenchmark model";
    }

    container test-status {
        leaf execStatus {
            type enumeration {
                enum "idle" {
                    value 1;
                }
                enum "executing" {
                    value 2;
                }
            }
            config false;
            mandatory true;
            description
                "Indicates whether a test run is in progress; only one test can run at a time";
        }
    }

    rpc start-test {
        description
          "Start a new performance test run";

        input {
            leaf operation {
                mandatory true;
                type enumeration {
                    enum "PERF RPC" {
                        value 1;
                        description
                          "The CRUD performance test using RPC's";
                    }
                    enum "PERF COAP" {
                        value 2;
                        description
                          "The CRUD performance test using CoAP";
                    }
                    enum "PERF HTTP" {
                        value 3;
                        description
                          "The CRUD performance test using HTTP";
                    }
                    enum "PERF MQTT" {
                        value 4;
                        description
                          "The CRUD performance test using MQTT";
                    }
                    enum "BASIC SANITY" {
                        value 5;
                        description
                          "CRUD one of each resource type";
                    }
                }
                description
                    "Type of the test to benchmark";
            }
            leaf numResources {
                type uint32;
                default 100000;
                description "Number of resources to test";
            }
            leaf numThreads {
                type uint32;
                default 32;
                description "Number of threads to use";
            }
            leaf serverUri {
                type string;
                default "coap://localhost";
                description
                  "Example: for coap://localhost, for http://localhost:8282";
            }
        }
        output {
            leaf status {
                mandatory true;
                type enumeration {
                    enum "OK" {
                        value 1;
                    }
                    enum "FAILED" {
                        value 2;
                    }
                    enum "TEST-IN-PROGRESS" {
                        value 3;
                    }
                }
                description
                    "Indicates whether the test finished successfully";
               }
            leaf createsPerSec {
                type uint32;
                default 1;
                description
                  "creates/second";
              }
            leaf retrievesPerSec {
                type uint32;
                default 1;
                description
                  "retrieves/second";
              }
            leaf deletesPerSec {
                type uint32;
                default 1;
                description
                  "deletes/second";
              }
            leaf crudsPerSec {
                type uint32;
                default 1;
                description
                  "cruds/second";
              }
        }
    }
}
