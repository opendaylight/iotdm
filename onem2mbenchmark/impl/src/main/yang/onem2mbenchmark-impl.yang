module onem2mbenchmark-impl {
    yang-version 1;
    namespace "urn:opendaylight:params:xml:ns:yang:onem2mbenchmark:impl";
    prefix "onem2mbenchmark-impl";

    import config { prefix config; revision-date 2013-04-05; }
    import opendaylight-md-sal-binding { prefix md-sal-binding; revision-date 2013-10-28;}

    description
        "Service definition for onem2mbenchmark project";

    revision "2014-12-10" {
        description
            "Initial revision";
    }

    identity onem2mbenchmark {
        base config:module-type;
        config:java-name-prefix Onem2mbenchmark;
    }

    augment "/config:modules/config:module/config:configuration" {
        case onem2mbenchmark {
            when "/config:modules/config:module/config:type = 'onem2mbenchmark'";
            container broker {
                uses config:service-ref {
                    refine type {
                        mandatory true;
                        config:required-identity md-sal-binding:binding-broker-osgi-registry;
                    }
                }
            }
            container rpc-registry {
                uses config:service-ref {
                    refine type {
                        mandatory true;
                        config:required-identity md-sal-binding:binding-rpc-registry;
                    }
                }
            }
        }
    }
}
