module onem2mexample-impl {
    yang-version 1;
    namespace "urn:opendaylight:params:xml:ns:yang:onem2mexample:impl";
    prefix "onem2mexample-impl";

    import config { prefix config; revision-date 2013-04-05; }
    import opendaylight-md-sal-binding { prefix md-sal-binding; revision-date 2013-10-28;}

    description
        "Service definition for onem2mexample project";

    revision "2014-12-10" {
        description
            "Initial revision";
    }

    identity onem2mexample {
        base config:module-type;
        config:java-name-prefix Onem2mexample;
    }

    augment "/config:modules/config:module/config:configuration" {
        case onem2mexample {
            when "/config:modules/config:module/config:type = 'onem2mexample'";
            container broker {
                uses config:service-ref {
                    refine type {
                        mandatory true;
                        config:required-identity md-sal-binding:binding-broker-osgi-registry;
                    }
                }
            }
        }
    }
}
