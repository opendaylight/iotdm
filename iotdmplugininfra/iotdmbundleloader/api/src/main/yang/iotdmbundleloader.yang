module iotdmbundleloader {
    yang-version 1;
    namespace "urn:opendaylight:params:xml:ns:yang:iotdm:iotdmbundleloader";
    prefix "iotdmbundleloader";

    revision "2015-01-05" {
        description "Initial revision of iotdmbundleloader model";
    }

    grouping bundles-to-load-list {
        description "Common definition of list of bundles to be loaded.";

        list bundles-to-load {
            key "priority";
            leaf priority {
                description "Priority defines ordering in which the bundles are loaded. " +
                            " Lower value indicates higher priority.";
                type uint32;
                mandatory true;
            }

            leaf iotdm-bundle-jar-location {
                description "Location of the JAR file including the bundle to be loaded.";
                type string;
                mandatory true;
            }
        }
    }

    grouping feature-definition {
        description "Data defining feature and it's bundles.";
        leaf bundle-loader-instance-name {
            description "BundleLoader instance name which the feature belongs to.";
            type string;
            mandatory true;
        }
        leaf feature-name {
            description "Name of the feature unique in the BundleLoader instance.";
            type string;
            mandatory true;
        }

        uses bundles-to-load-list;
    }

    grouping bundle-loader-feature {
        description "Data which identifies specific feature of specific BundleLoader instance.";
        leaf bundle-loader-instance-name {
            description "Name of the BundleLoader instance.";
            type string;
            mandatory true;
        }
        leaf feature-name {
            description "Name of the feature.";
            type string;
            mandatory true;
        }
    }

    rpc feature-put {
        description "Adds or updates feature.";
        input {
            uses feature-definition;
        }

        output {
        }
    }

    rpc feature-remove {
        description "Removes feature.";
        input {
            uses bundle-loader-feature;
        }

        output {
        }
    }

    rpc clean {
        description "Removes all features of the specific BundleLoader instance.";
        input {
            leaf bundle-loader-instance-name {
                type string;
                mandatory true;
            }
        }

        output {
        }
    }

    rpc feature-reload {
        description "Reloads all bundles of the feature.";
        input {
           uses bundle-loader-feature;
        }

        output {
        }
    }

    rpc running-config {
        description "Collects data of the features which are currently loaded.";
        input {
            leaf bundle-loader-instance-name {
                type string;
                mandatory false;
            }
            leaf feature-name {
                type string;
                mandatory false;
            }
        }

        output {
            list running-config-list {
                key bundle-loader-instance-name;
                leaf bundle-loader-instance-name {
                    type string;
                    mandatory true;
                }

                list running-features {
                    key "feature-name";
                    leaf feature-name {
                        type string;
                    }

                    list running-feature-bundles {
                        key "priority";
                        leaf priority {
                            type uint32;
                            mandatory true;
                        }

                        leaf iotdm-bundle-jar-location {
                            type string;
                            mandatory true;
                        }

                        leaf bundle-name {
                            type string;
                            mandatory true;
                        }

                        leaf bundle-version {
                            type string;
                            mandatory true;
                        }

                        leaf bundle-id {
                            type string;
                            mandatory true;
                        }

                        leaf bundle-state {
                            type string;
                            mandatory true;
                        }

                        leaf bundle-diagnostic-info {
                            type string;
                        }
                    }
                }
            }
        }
    }

    grouping bundle-loader-startup-features {
        description "Definition of list of feature definitions stored in persistent configuration.";

        list startup-features {
            description "List of features stored in persisten configuration.";

            key "feature-name";
            leaf feature-name {
                description "Name of the feature.";
                type string;
                mandatory true;
            }

            uses bundles-to-load-list;
        }
    }

    grouping startup-config-content {
        description "Definition of the content of the persistent configuration.";

        list startup-config-list {
            description "List of startup feature configurations per BundleLoader instance.";

            key bundle-loader-instance-name;
            leaf bundle-loader-instance-name {
                description "Name of the BundleLoader instance.";
                type string;
                mandatory true;
            }

            uses bundle-loader-startup-features;
        }
    }

    rpc startup-config {
        description "Collects information from persistent configuration.";

        input {
            leaf bundle-loader-instance-name {
                description "Name of the BundleLoader instance.";
                type string;
                mandatory false;
            }
            leaf feature-name {
                description "Name of the feature.";
                type string;
                mandatory false;
            }
        }

        output {
            uses startup-config-content;
        }
    }

    container bundle-loader-startup-config {
        description "The permanent configuration stored in the persistent data store.";
        uses startup-config-content;
    }
}
